module basic-remote-attestation {
  namespace "urn:ietf:params:xml:ns:yang:brat";
  prefix "yang-brat";
  
  import ietf-yang-types {
    prefix yang;
  }
  import ietf-hardware {
      prefix ietfhw;
  }
  import ietf-crypto-types {
      prefix ietfct;
  }
  
  organization
   "Fraunhofer SIT";
  contact
   "Henk Birkholz
    Fraunhofer Institute for Secure Information Technology
    Email: henk.birkholz@sit.fraunhofer.de";
  description
    "A YANG module to enable a TPM 2.0 based remote attestation
     procedure.
     Copyright (C) Fraunhofer SIT (2018).";
  revision "2018-06-15" {
  description
    "Initial version";
  reference
    "draft-birkholz-yang-basic-remote-attestation";
  }
  
  grouping hash-algo {
    choice algo-registry-type {
      mandatory true;
      description
        "Unfortunately, both IETF and TCG have registries here.
        Choose your weapon wisely.";
      case tcg {
        description
          "you chose the east door, the tcg space opens up to
          you.";
        leaf tcg-hash-algo-id {
          description
            "This is an index referencing the TCG Algorithm
            Registry based on TPM_ALG_ID.";
          type uint16;
        }
      }
      case ietf {
        description
          "you chose the west door, the ietf space opens up to
          you.";
        leaf ietf-ni-hash-algo-id {
          description
            "This is an index referencing the Named Information
             Hash Algorithm Registry.";
          type uint8;
        }
      }
    }
  }
  
  grouping hash {
    list hash-digests {
      container hash-digest {
        description
          "A hash value based on a hash algorithm registered by an
          SDO.";
        uses hash-algo;
        leaf hash-value {
          description
            "The binary representaion of the hash value.";
          type binary;
        }
      }
    }
  }
  
  grouping nonce {
    leaf nonce-value {
      mandatory true;
      description
        "This nonce SHOULD be generated via a registered
        cryptographic-strength algorithm. In consequence, the length
        of the nonce depends on the hash algorithm used. The algorithm
        used in this case is independent from the hash algorithm used to
        create the hash-value in the response of the attestor.";
      type binary;
    }
  }
  
  grouping pcr-selection {
    description
      "A Verifier can request one or more PCR values uses its
      individually created AC. The corresponding selection filter is
      represented in this grouping. Requesting a PCR value that is not in 
      scope of the AC used, detailed exposure via error msg should be
      avoided.";
    list pcr-list {
      description
        "For each PCR in this list an individual list of banks (hash-algo)
        can be requested. It depends on the datastore, if every bank in 
        this grouping is included per PCR (crude), or if each requested
        bank set is returned for each PCR individually (elegant).";
      container pcr {
        description
          "The composite of a PCR number and corresponding bank numbers.";
        leaf-list pcr-numbers {
           description
             "The number of the PCR. At the moment this is limited
             32";
           type uint8;
        }
        uses hash-algo;
      }
    }
  }
  
  grouping pcr-selector {
    description
      "A Verifier can request the generation of an attestation
      certificate (a signed public attestation key
      (non-migratable, tpm-resident) wrt one or more PCR values.
      The corresponding creation input is represented in this grouping.
      Requesting a PCR value that is not supported results in an error,
      detailed exposure via error msg should be avoided.";
    list pcr-list {
      description
        "For each PCR in this list an individual hash-algo can be
        requested.";
      container pcr {
        description
          "The composite of a PCR number and corresponding bank numbers.";
        leaf-list pcr-index {
           description
             "The numbers of the PCRs that are associated with
             the created key. At the moment the highest number is 32";
           type uint8;
        }
        uses hash-algo;
      }
    }
  }
  
  grouping signature-scheme {
    choice signature-identifier-type {
      mandatory true;
      description
        "There are multiple ways to reference a signature type.
        This used to select the signature algo to sign the quote
        information response.";
      case TPM_ALG_ID {
        description
          "This references the indices of table 9 in the TPM 2.0 structure specification.";
        leaf TPM_ALG_ID-value {
          description
            "The TPM Algo ID.";
          type uint16;
        }
      }
      case COSE_Algorithm {
        description
          "This references the IANA COSE Algorithms Registry indices. Every index of this
          registry to be used must be mapable to a TPM_ALG_ID value.";
        leaf COSE_Algorithm-value {
          description
            "The TPM Algo ID.";
          type int32;
        }
      }
    }
  }
  
  grouping attestation-key-identifier {
    choice key-identifier {
      description
        "Identifier for the attestation key to use for signing
        attestation evidence.";
      case public-key {
        description
          "Use the public part of a key pair to identify the
          attestation key.";
        leaf pub-key-id {
          description
            "The value of the identifier for the public key.";
          type binary;
        }
      }
      case uuid {
        description
          "Use a YANG agent generated (and maintained) attestation
          key UUID.";
        leaf uuid-value {
          description
            "The UUID identifying the corresponding public key.";
          type binary;
        }
      }
    }
  }
  
 grouping tpm-name {
   description
     "In a system with multiple-TPMs get the data from a specific TPM
      identified by the name and physical-index.";
   leaf tpm_name {
      type string;
      description
      "Name of the TPM or All";
   }
   leaf tpm-physical-index {
       if-feature ietfhw:entity-mib;
       type int32 {
            range "1..2147483647";
       }
       config false;
       description
            "The entPhysicalIndex for the TPM.";
        reference
            "RFC 6933: Entity MIB (Version 4) - entPhysicalIndex";
     }
 }
 grouping compute-node {
   description
     "In a distributed system with multiple compute nodes
      this is the node identified by name and physical-index.";
   leaf node-name {
      type string;
      description
      "Name of the compute node or All";
   }
   leaf node-physical-index {
       if-feature ietfhw:entity-mib;
       type int32 {
            range "1..2147483647";
       }
       config false;
       description
            "The entPhysicalIndex for the compute node.";
        reference
            "RFC 6933: Entity MIB (Version 4) - entPhysicalIndex";
     }
 }

 grouping node-uptime {
   description
     "Uptime in seconds of the node.";
   leaf up-time {
     type uint32;
     description
     "Uptime in seconds of this node reporting its data";
   }
 }

  identity log-type {
    description
      "The type of logs available.";
  }

  identity bios {
    base log-type;
    description
      "Measurement log created by the BIOS/UEFI.";
  }

  identity ima {
    base log-type;
    description
      "Measurement log created by IMA.";
  }

  identity ima-binary {
    base log-type;
    description
      "Measurement log created by IMA in binary encoding.";
  }
    
  grouping log-identifier {
    description
      "Identifier for type of log to be retrieved.";
    leaf measurement-log-type {
      mandatory true;
      type identityref {
        base log-type;
      }
    }
  }


grouping boot-event-log {
  description
    "Defines an event log corresponding to the event that extended the PCR";
  leaf event-number {
      type uint32;
      description
  "Unique event number of this event";
  }
  leaf event-type {
      type uint32;
      description
  "log event type";
  }
  leaf pcr-index {
     type uint16;
     description
 "Defines the PCR index that this event extended";
  }
  list digest-list {
    description "Hash of event data";
    uses hash-algo;
    leaf-list digest {
      type binary;
      description
      "The hash of the event data";
    }
  }
   leaf event-size {
     type uint32;
     description
     "Size of the event data";
   }
   leaf-list event-data {
     type uint8;
     description
     "the event data size determined by event-size";
   }
}

 grouping ima-event {
   description
     "Defines an hash log extend event for IMA measurements";
   leaf event-number {
       type uint64;
       description
  "Unique number for this event for sequencing";
     }
   leaf ima-template {
     type string;
     description
     "Name of the template used for event logs
     for e.g. ima, ima-ng";
   }
   leaf filename-hint {
       type string;
       description
   "File that was measured";
   }
   leaf filedata-hash {
       type binary;
       description
    "Hash of filedata";
   }
  leaf template-hash-algorithm {
    type string;
    description
     "Algorithm used for template-hash";
   }
   leaf template-hash {
  type binary;
  description
   " hash(filedata-hash, filename-hint)";
   }
   leaf pcr-index {
      type uint16;
      description
  "Defines the PCR index that this event extended";
   }
   leaf signature {
     type binary;
     description
     "The file signature";
   }
 }

  grouping bios-event-log {
    description
    "Measurement log created by the BIOS/UEFI.";
    list bios-event-entry {
      key event-number;
       description
       "Ordered list of TCG described event log
        that extended the PCRs in the order they
        were logged";
        uses boot-event-log;
     }
  }

  grouping ima-event-log {
    description
      "Measurement log created by IMA.";
    list ima-event-entry {
      key event-number;
      description
      "Ordered list of ima event logs by event-number";
       uses ima-event;
     }
  }

  grouping event-logs {
    choice log-type {
      mandatory true;
      description
        "Event log type determines the event logs content.";

      case bios {
        description
          "BIOS/UEFI event logs";
        container bios-event-logs {
          description
            "The requested entries of the bios log.";
          uses bios-event-log;
        }
      }
      case ima {
        description
          "IMA event logs";
	container ima-event-logs {
          description
            "The requested entries of the ima log.";
          uses ima-event-log;
        }
      }
      case ima-binary {
        description
          "IMA event logs encoded in binary representation";
        leaf-list ima-event-logs-compressed {
          description
            "The requested entries of the ima log.";
            type binary;
        }
      }      
    }
  }


  rpc tpm2-challenge-response-attestation {
    description
      "This RPC accepts the input for TSS commands of the managed device.
      ComponentIndex from the hardware manager YANG module to refer to 
      dedicated TPM in composite devices, e.g. smart NICs, is still a 
      TODO.";
    input {
      container tpm2-attestation-challenge {
        description
          "This container includes every information element defined
           in the reference challenge-response interaction model for
           remote attestation. Corresponding values are based on
           TPM 2.0 structure definitions";
        uses pcr-selection;
        uses nonce;
        uses signature-scheme;
        uses attestation-key-identifier;
      }
      uses tpm-name;
    }
    output {
      list tpm2-attestation-response {
        key tpm_name;
        description
          "The binary output of TPM2b_Quote. An TPMS_ATTEST structure
          including a length, encapsulated in a signature";
	uses tpm-name;
	uses node-uptime;
	uses compute-node;
        container tpms-attest {
          description
            "A composite of value and length and list of selected
            pcrs (original name: [type]attested)";
          leaf pcrdigest {
            description
              "split out value of TPMS_QUOTE_INFO for convenience";
            type binary;
          }
          leaf tpms-attest-result {
            description
              "The complete TPM generate structure including signature.";
            type binary;
          }
        }
        leaf tpmt-signature {
          description
             "split out value of the signature for convenience";
          type binary;
        }
      }
    }
  }
  
  rpc basic-trust-establishment {
    description
      "This RPC creates a tpm-resident, non-migratable key to be used
      in TPM_Quote commands, an attestation certificate.";
    input {
      uses nonce;
      uses signature-scheme;
      uses tpm-name;
      leaf certificate-name {
         type string;
         description
         "An arbitrary name for the identity certificate chain requested.";
      }
    }
    output {
    list attestation-certificates {
      key tpm_name;
      description
        "Attestation Certificate data from a TPM identified by the TPM name";
      uses tpm-name;
      uses node-uptime;
      uses compute-node;
      leaf certificate-name {
         type string;
         description
         "An arbitrary name for this identity certificate or certificate chain.";
      }      
      leaf attestation-certificate {
        description
          "The binary signed certificate chain data for this identity certificate.";
        type ietfct:end-entity-cert-cms;
      }
      uses attestation-key-identifier;
    }
    }
  }
  
  rpc log-retrieval {
    description
      "Logs Entries are either identified via indices or via providing
      the last line received. The number of lines returned can be limited.
      The type of log is a choice that can be
      augmented.";
    input {
      list log-selector {
        key node-name;
        description
	 "Selection of log entries to be reported.";
	uses compute-node;
        choice index-type {
          description
             "Last log entry received, log index number, or timestamp.";

          case last-entry {
            description
              "The last entry of the log already retrieved.";
            leaf last-entry-value {
              description
              "Content of an log event which matches 1:1 with a 
              unique event record contained within the log.  Log 
              entries subsequent to this will be passed to the 
              requestor.  Note: if log entry values are not unique, 
              this MUST return an error.";
	      type binary;
            }
          }
          case index {
	    description
              "Numeric index of the last log entry retrieved, or zero.";
            leaf index-number {
              description
              "The numeric index number of a log entry.  Zero means 
              to start at the beginning of the log.   Entries
              subsequent to this will be passed to the 
              requestor.";
              type uint64;
            }
          }
          case timestamp {
            leaf timestamp {
              type yang:date-and-time;
              description
                "Timestamp from which to start the extraction.  The next
                log entry subsequent to this timestamp is to be sent.";
            }
            description
              "Timestamp from which to start the extraction.";
          }
        }
      }
      uses log-identifier;
      uses pcr-selection;
      leaf log-entry-quantity {
        type uint16;
        description
         "The number of log entries to be returned. If omitted, it 
         means all of them.";
      }
    } 
    output {
      container system-event-logs {
         description
	 "The requested data of the measurement event logs";
         list node-data {
           key node-name;
           description
           "Event logs of a node in a distributed system
            identified by the node name";
           uses compute-node;
	   uses node-uptime;
	   list tpm-updated {
	     key tpm_name;
	     description
	     "TPM these events may have recorded data in";
	     uses tpm-name;
	   }
           container log-result {
             description
             "The requested entries of the corresponding log.";
	     uses event-logs;
   	   }
         }
       }
     }
   }
 
  
  container rats-support-structures {
    leaf-list supported-algos {
      description
        "Supported TPM_ALG_ID values for the TPM in question.
        Will include ComponentIndex soon.";
      type uint16;
    }
    leaf endorsement-certificate {
      description
        "The signed pulic endorsement key (EK) and corresponding claims (EK Certificate). In a TPM 2.0 the EK Certificate resides in a well-defined NVRAM location by the TPM vednor.";
      type binary;
      mandatory true;
    }
  }
}
