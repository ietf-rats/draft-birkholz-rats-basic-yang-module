module ietf-basic-remote-attestation {
  namespace "urn:ietf:params:xml:ns:yang:ietf-basic-remote-attestation";
  prefix "yang-brat";
  
  import ietf-yang-types {
    prefix yang;
  }
  import ietf-hardware {
      prefix ietfhw;
  }
  import ietf-crypto-types {
      prefix ietfct;
  }
  
  organization
   "Fraunhofer SIT";
  contact
   "Henk Birkholz
    Fraunhofer Institute for Secure Information Technology
    Email: henk.birkholz@sit.fraunhofer.de";
  description
    "A YANG module to enable a TPM 2.0 based remote attestation
     procedure.
     Copyright (C) Fraunhofer SIT (2018).";
  revision "2018-06-15" {
  description
    "Initial version";
  reference
    "draft-birkholz-yang-basic-remote-attestation";
  }
  
  grouping hash-algo {
    description
      "A selector for the hashing algorithm";
    choice algo-registry-type {
      mandatory true;
      description
        "Unfortunately, both IETF and TCG have registries here.
        Choose your weapon wisely.";
      case tcg {
        description
          "you chose the east door, the tcg space opens up to
          you.";
        leaf tcg-hash-algo-id {
          type uint16;
          description
            "This is an index referencing the TCG Algorithm
            Registry based on TPM_ALG_ID.";
        }
      }
      case ietf {
        description
          "you chose the west door, the ietf space opens up to
          you.";
        leaf ietf-ni-hash-algo-id {
          type uint8;
          description
            "This is an index referencing the Named Information
             Hash Algorithm Registry.";
        }
      }
    }
  }
  
  grouping hash {
    description
      "The hash value including hash-algo identifier";
    list hash-digests {
      description
        "The list of hashes.";
      container hash-digest {
        description
          "A hash value based on a hash algorithm registered by an
          SDO.";
        uses hash-algo;
        leaf hash-value {
          type binary;
          description
            "The binary representation of the hash value.";
        }
      }
    }
  }
  
  grouping nonce {
    description
      "A nonce to show freshness and counter replays.";
    leaf nonce-value {
      type binary;
      mandatory true;
      description
        "This nonce SHOULD be generated via a registered
        cryptographic-strength algorithm. In consequence, the length
        of the nonce depends on the hash algorithm used. The algorithm
        used in this case is independent from the hash algorithm used to
        create the hash-value in the response of the attestor.";
    }
  }

  grouping tpm12-pcr-selection {
    description
      "A Verifier can request one or more PCR values using its
      individually created Attestation Key Certificate (AC).
      The corresponding selection filter is represented in this grouping.
      Requesting a PCR value that is not in scope of the AC used, detailed
      exposure via error msg should be avoided.";
    leaf-list pcr-indices {
      type uint8;
      description
        "The numbers/indexes of the PCRs. At the moment this is limited
        to 32.";
    }
  }

  grouping tpm20-pcr-selection {
    description
      "A Verifier can request one or more PCR values uses its
      individually created AC. The corresponding selection filter is
      represented in this grouping. Requesting a PCR value that is not
      in scope of the AC used, detailed exposure via error msg should
      be avoided.";
    list pcr-list {
      description
        "For each PCR in this list an individual list of banks
        (hash-algo) can be requested. It depends on the datastore, if
        every bank in this grouping is included per PCR (crude), or if
         each requested bank set is returned for each PCR individually
        (elegant).";
      container pcr {
        description
          "The composite of a PCR number and corresponding bank
          numbers.";
        leaf-list pcr-indices {
           type uint8;
           description
             "The number of the PCR. At the moment this is limited
             32";
        }
        uses hash-algo;
      }
    }
  }

  grouping pcr-selector {
    description
      "A Verifier can request the generation of an attestation
      certificate (a signed public attestation key
      (non-migratable, tpm-resident) wrt one or more PCR values.
      The corresponding creation input is represented in this grouping.
      Requesting a PCR value that is not supported results in an error,
      detailed exposure via error msg should be avoided.";
    list pcr-list {
      description
        "For each PCR in this list an individual hash-algo can be
        requested.";
      container pcr {
        description
          "The composite of a PCR number and corresponding bank
          numbers.";
        leaf-list pcr-index {
           type uint8;
           description
             "The numbers of the PCRs that are associated with
             the created key. At the moment the highest number is 32";
        }
        uses hash-algo;
      }
    }
  }

  grouping tpm12-signature-scheme {
    description
      "The signature scheme used to sign the evidence via a TPM 1.2.";
    leaf TPM_SIG_SCHEME-value {
      type uint8;
      mandatory true;
      description
        "Selects the signature scheme that is used to sign the TPM quote
        information response. Allowed values can be found in the table at
        the bottom of page 32 in the TPM 1.2 Structures specification
        (Level 2 Revision 116, 1 March 2011).";
    }
  }

  grouping tpm20-signature-scheme {
    description
      "The signature scheme used to sign the evidence.";
    choice signature-identifier-type {
      mandatory true;
      description
        "There are multiple ways to reference a signature type.
        This used to select the signature algo to sign the quote
        information response.";
      case TPM_ALG_ID {
        description
          "This references the indices of table 9 in the TPM 2.0
          structure specification.";
        leaf TPM_ALG_ID-value {
          type uint16;
          description
            "The TPM Algo ID.";
        }
      }
      case COSE_Algorithm {
        description
          "This references the IANA COSE Algorithms Registry indices.
          Every index of this registry to be used must be mapable to a
          TPM_ALG_ID value.";
        leaf COSE_Algorithm-value {
          type int32;
          description
            "The TPM Algo ID.";
        }
      }
    }
  }

  grouping tpm12-attestation-key-identifier {
    description
      "A selector for a suitable key identifier for a TPM 1.2.";
    choice key-identifier {
      description
        "Identifier for the attestation key to use for signing
        attestation evidence.";
      case public-key {
        leaf pub-key-id {
          type binary;
          description
            "The value of the identifier for the public key.";
        }
      }
      case TSS_UUID {
        description
          "Use a YANG agent generated (and maintained) attestation
          key UUID that complies with the TSS_UUID datatype of the TCG
          Software Stack (TSS) Specification, Version 1.10 Golden,
          August 20, 2003.";
        container TSS_UUID-value {
          description
            "A detailed structure that is used to create the
            TPM 1.2 native TSS_UUID as defined in the TCG Software
            Stack (TSS) Specification, Version 1.10 Golden,
            August 20, 2003.";
          leaf ulTimeLow {
            type uint32;
            description
              "The low field of the timestamp.";
          }
          leaf usTimeMid {
            type uint16;
            description
              "The middle field of the timestamp.";
          }
          leaf usTimeHigh {
            type uint16;
            description
              "The high field of the timestamp multiplexed with the
              version number.";
          }
          leaf bClockSeqHigh {
            type uint8;
            description
              "The high field of the clock sequence multiplexed with
              the variant.";
          }
          leaf bClockSeqLow {
            type uint8;
            description
              "The low field of the clock sequence.";
          }
          leaf-list rgbNode {
            type uint8;
            description
              "The spatially unique node identifier.";
          }
        }
      }
    }
  }

  grouping tpm20-attestation-key-identifier {
    description
      "A selector for a suitable key identifier.";
    choice key-identifier {
      description
        "Identifier for the attestation key to use for signing
        attestation evidence.";
      case public-key {
        leaf pub-key-id {
          type binary;
          description
            "The value of the identifier for the public key.";
        }
      }
      case uuid {
        description
          "Use a YANG agent generated (and maintained) attestation
          key UUID.";
        leaf uuid-value {
          type binary;
          description
            "The UUID identifying the corresponding public key.";
        }
      }
    }
  }

  grouping tpm-identifier {
    description
      "In a system with multiple-TPMs get the data from a specific TPM
       identified by the name and physical-index.";
    leaf tpm-name {
      type string;
      description
        "Name of the TPM or All";
    }
    leaf tpm-physical-index {
      if-feature ietfhw:entity-mib;
      type int32 {
        range "1..2147483647";
      }
      config false;
      description
        "The entPhysicalIndex for the TPM.";
      reference
        "RFC 6933: Entity MIB (Version 4) - entPhysicalIndex";
    }
  }
  grouping compute-node-identifier {
    description
      "In a distributed system with multiple compute nodes
       this is the node identified by name and physical-index.";
    leaf node-id {
       type string;
       description
         "Compute node ID, such as Board Serial Number.";
    }
    leaf node-physical-index {
      if-feature ietfhw:entity-mib;
      type int32 {
        range "1..2147483647";
      }
      config false;
       description
         "The entPhysicalIndex for the compute node.";
       reference
         "RFC 6933: Entity MIB (Version 4) - entPhysicalIndex";
    }
  }

  grouping tpm12-pcr-info-short {
    description
      "This structure is for defining a digest at release when the only
      information that is necessary is the release configuration.";
    uses tpm12-pcr-selection;
    leaf locality-at-release {
      type uint8;
      description
        ".This SHALL be the locality modifier required to release the
        information (TPM 1.2 type TPM_LOCALITY_SELECTION)";
    }
    leaf digest-at-release {
      type binary;
        description
          "This SHALL be the digest of the PCR indices and PCR values
          to verify when revealing auth data (TPM 1.2 type
          TPM_COMPOSITE_HASH).";
    }
  }

  grouping tpm12-version {
    description
      "This structure provides information relative the version of
      the TPM.";
    list version {
      description
        "This indicates the version of the structure
        (TPM 1.2 type TPM_STRUCT_VER). This MUST be 1.1.0.0.";
      leaf major {
        type uint8;
        description
          "Indicates the major version of the structure.
          MUST be 0x01.";
      }
      leaf minor {
        type uint8;
        description
          "Indicates the minor version of the structure.
          MUST be 0x01.";
      }
      leaf revMajor {
        type uint8;
        description
         "Indicates the rev major version of the structure.
         MUST be 0x00.";
      }
      leaf revMinor {
        type uint8;
        description
          "Indicates the rev minor version of the structure.
          MUST be 0x00.";
      }
    }
  }

  grouping tpm12-quote-info-common {
    description
      "These statements are used in bot quote variants of the TPM 1.2";
    leaf fixed {
      type binary;
      description
        "This SHALL always be the string ‘QUOT’ or ‘QUO2’
        (length is 4 bytes).";
    }
    leaf external-data {
      type binary;
      description
        "160 bits of externally supplied data, typically a nonce.";
    }
    leaf signature-size {
      type uint32;
      description
       "The size of TPM 1.2 'signature' value.";
    }
    leaf signature {
      type binary;
      description
        "Signature over SHA-1 hash of tpm12-quote-info2'.";
    } 
  }

  grouping tpm12-quote-info {
    description
      "This structure provides the mechanism for the TPM to quote the
      current values of a list of PCRs (as used by the TPM_Quote2
      command).";
    uses tpm12-version;
    leaf digest-value {
      type binary;
      description
        "This SHALL be the result of the composite hash algorithm using
        the current values of the requested PCR indices
        (TPM 1.2 type TPM_COMPOSITE_HASH.)";
    }
  }

  grouping tpm12-quote-info2 {
    description
      "This structure provides the mechanism for the TPM to quote the
      current values of a list of PCRs
     (as used by the TPM_Quote2 command).";
    leaf tag {
      type uint8;
      description
        "This SHALL be TPM_TAG_QUOTE_INFO2.";
    }
    uses tpm12-pcr-info-short;
  }

  grouping tpm12-cap-version-info {
    description
      "TPM returns the current version and revision of the TPM 1.2 .";
    list TPM_PCR_COMPOSITE {
      description
        "The TPM 1.2 TPM_PCRVALUEs for the pcr-indices.";
      uses tpm12-pcr-selection;
      leaf value-size {
        type uint32;
        description
          "This SHALL be the size of the 'tpm12-pcr-value' field
          (not the number of PCRs).";
      }
      leaf-list tpm12-pcr-value {
        type binary;
        description
          "The list of TPM_PCRVALUEs from each PCR selected in sequence
          of tpm12-pcr-selection.";
      }
      list version-info {
        description
          "An optional output parameter from a TPM 1.2 TPM_Quote2.";
        leaf tag {
          type uint16;
          description
            "The TPM 1.2 version and revision
            (TPM 1.2 type TPM_STRUCTURE_TAG).
            This MUST be TPM_CAP_VERSION_INFO (0x0030)";
        }
        uses tpm12-version;
        leaf spec-level {
          type uint16;
          description
            "A number indicating the level of ordinals supported.";
        }
        leaf errata-rev {
          type uint8;
          description
            "A number indicating the errata version of the
            specification.";
        }
        leaf tpm-vendor-id {
          type binary;
          description
            "The vendor ID unique to each TPM manufacturer.";
        }
        leaf vendor-specific-size {
          type uint16;
          description
            "The size of the vendor-specific area.";
        }
        leaf vendor-specific {
          type binary;
          description
            "Vendor specific information.";
        }
      }
    }
  }

  grouping tpm12-pcr-composite {
    description
      "The actual values of the selected PCRs (a list of TPM_PCRVALUEs
      (binary)and associated metadata for TPM 1.2.";
    list TPM_PCR_COMPOSITE {
      description
        "The TPM 1.2 TPM_PCRVALUEs for the pcr-indices.";
      uses tpm12-pcr-selection;
      leaf value-size {
        type uint32;
        description
          "This SHALL be the size of the 'tpm12-pcr-value' field
          (not the number of PCRs).";
      }
      leaf-list tpm12-pcr-value {
        type binary;
        description
          "The list of TPM_PCRVALUEs from each PCR selected in sequence
          of tpm12-pcr-selection.";
      }
    }
  }

  grouping node-uptime {
    description
      "Uptime in seconds of the node.";
    leaf up-time {
      type uint32;
      description
        "Uptime in seconds of this node reporting its data";
    }
  }

  identity log-type {
    description
      "The type of logs available.";
  }

  identity bios {
    base log-type;
    description
      "Measurement log created by the BIOS/UEFI.";
  }

  identity ima {
    base log-type;
    description
      "Measurement log created by IMA.";
  }

  grouping log-identifier {
    description
      "Identifier for type of log to be retrieved.";
    leaf log-type {
      type identityref {
        base log-type;
      }
      mandatory true;
      description
        "The corresponding measurement log type identity.";
    }
  }

  grouping boot-event-log {
    description
      "Defines an event log corresponding to the event that extended the
      PCR";
    leaf event-number {
      type uint32;
      description
        "Unique event number of this event";
    }
    leaf event-type {
        type uint32;
        description
          "log event type";
    }
    leaf pcr-index {
      type uint16;
      description
        "Defines the PCR index that this event extended";
    }
    list digest-list {
      description "Hash of event data";
      uses hash-algo;
      leaf-list digest {
        type binary;
        description
          "The hash of the event data";
      }
    }
    leaf event-size {
      type uint32;
      description
        "Size of the event data";
    }
    leaf-list event-data {
      type uint8;
      description
        "the event data size determined by event-size";
    }
  }

  grouping ima-event {
    description
      "Defines an hash log extend event for IMA measurements";
    leaf event-number {
      type uint64;
      description
        "Unique number for this event for sequencing";
    }
    leaf ima-template {
      type string;
      description
        "Name of the template used for event logs
        for e.g. ima, ima-ng, ima-sig";
    }
    leaf filename-hint {
      type string;
      description
        "File that was measured";
    }
    leaf filedata-hash {
      type binary;
      description
        "Hash of filedata";
    }
    leaf filedata-hash-algorithm {
      type binary;
      description
	"Algorithm used for filedata hash";
    }
    leaf template-hash-algorithm {
      type string;
      description
        "Algorithm used for template-hash";
    }
    leaf template-hash {
      type binary;
      description
        "hash(filedata-hash, filename-hint)";
    }
    leaf pcr-index {
      type uint16;
      description
        "Defines the PCR index that this event extended";
    }
    leaf signature {
      type binary;
      description
        "The file signature";
    }
  }

  grouping bios-event-log {
    description
    "Measurement log created by the BIOS/UEFI.";
    list bios-event-entry {
      key event-number;
       description
       "Ordered list of TCG described event log
        that extended the PCRs in the order they
        were logged";
        uses boot-event-log;
     }
  }

  grouping ima-event-log {
    list ima-event-entry {
      key event-number;
      description
      "Ordered list of ima event logs by event-number";
       uses ima-event;
    }
    description
      "Measurement log created by IMA.";
  }

  grouping event-logs {
    description
      "A selector for the log and its type.";
    choice log-type {
      mandatory true;
      description
        "Event log type determines the event logs content.";
      case bios {
        description
          "BIOS/UEFI event logs";
        container bios-event-logs {
          description
            "This is an index referencing the TCG Algorithm
            Registry based on TPM_ALG_ID.";
          uses bios-event-log;
        }
      }
      case ima {
        description
          "IMA event logs";
        container ima-event-logs {
          description
            "This is an index referencing the TCG Algorithm
            Registry based on TPM_ALG_ID.";
          uses ima-event-log;
        }
      }
    }
  }

  rpc tpm12-challenge-response-attestation {
    description
      "This RPC accepts the input for TSS TPM 1.2 commands of the
       managed device. ComponentIndex from the hardware manager YANG
       module to refer to dedicated TPM in composite devices,
       e.g. smart NICs, is still a TODO.";
    input {
      container tpm1-attestation-challenge {
        description
          "This container includes every information element defined
           in the reference challenge-response interaction model for
           remote attestation. Corresponding values are based on
           TPM 1.2 structure definitions";
        uses tpm12-pcr-selection;
        uses nonce;
        uses tpm12-signature-scheme;
        uses tpm12-attestation-key-identifier;
        leaf add-version {
          type boolean;
          description
            "Whether or not to include TPM_CAP_VERSION_INFO; if true,
             then TPM_Quote2 must be used to create the response.";
        }
        uses tpm-name;
      }
    }
    output {
      list tpm12-attestation-response {
        key tpm_name;
        description
          "The binary output of TPM 1.2 TPM_Quote/TPM_Quote2, including
           the PCR selection and other associated attestation evidence
           metadata";
        uses tpm-name;
        uses node-uptime;
        uses compute-node;
        uses tpm12-quote-info-common;
        choice tpm12-quote {
          mandatory true;
          description
            "Either a tpm12-quote-info or tpm12-quote-info2, depending
            on whether TPM_Quote or TPM_Quote2 was used
            (cf. input field add-verson).";
          case tpm12-quote1 {
            description
              "BIOS/UEFI event logs";
            uses tpm12-quote-info;
            uses tpm12-pcr-composite;
          }
          case tpm12-quote2 {
            description
              "BIOS/UEFI event logs";
            uses tpm12-quote-info2;
          }
        }
      }
    }
  }

  rpc tpm20-challenge-response-attestation {
    description
      "This RPC accepts the input for TSS TPM 2.0 commands of the
       managed device. ComponentIndex from the hardware manager YANG
       module to refer to dedicated TPM in composite devices,
       e.g. smart NICs, is still a TODO.";
    input {
      container tpm20-attestation-challenge {
        description
          "This container includes every information element defined
           in the reference challenge-response interaction model for
           remote attestation. Corresponding values are based on
           TPM 2.0 structure definitions";
        uses nonce;
	list challenge-objects {
	  key "node-id tpm-name";
	  description
	    "Nodes to fetch the attestation information, PCR selection and AK identifier.";
	    uses compute-node-identifier;
	    uses tpm-identifier;
	    uses tpm20-pcr-selection;
	    uses tpm20-signature-scheme;
	    uses tpm20-attestation-key-identifier;
	}
      }
    }
    output {
      list tpm20-attestation-response {
        key "node-id tpm-name";
        description
          "The binary output of TPM2b_Quote in one TPM chip of the node which identified by node-id. An TPMS_ATTEST structure including a length, encapsulated in a signature";
        uses tpm-identifier;
        uses node-uptime;
        uses compute-node-identifier;

	leaf quote {
	  type binary;
	  description
	    "Quote data returned by TPM Quote, including PCR selection, PCR digest and etc.";
	}
        leaf quote-signature {
          type binary;
          description
            "Quote signature returned by TPM Quote.";
        }
	list pcr-bank-values {
	  key algo-registry-type;
	  description
	    "PCR values in each PCR bank.";
	  uses hash-algo;
	    
	  list pcr-values {
	    key pcr-index;
	    description
	      "List of one PCR bank.";
	    leaf pcr-index {
	      type uint16;
	      description
		"PCR index number.";
	    }
	    leaf pcr-value {
	      type string;
	      description
		"PCR value.";
	    }
	  }
	}
	leaf pcr-digest-algo-in-quote {
	  uses hash-algo;
	  description
	    "The hash algorithm for PCR value digest in quote.";
	}
      }
    }
  }

  rpc basic-trust-establishment {
    description
      "This RPC creates a tpm-resident, non-migratable key to be used
      in TPM_Quote commands, an attestation certificate.";
    input {
      uses nonce;
      uses tpm20-signature-scheme;
      uses tpm-identifier;
      leaf certificate-name {
         type string;
         description
           "An arbitrary name for the identity certificate chain
           requested.";
      }
    }
    output {
      list attestation-certificates {
        key tpm-name;
        description
          "Attestation Certificate data from a TPM identified by the TPM
          name";
        uses tpm-identifier;
        uses node-uptime;
        uses compute-node-identifier;
        leaf certificate-name {
          type string;
          description
            "An arbitrary name for this identity certificate or
            certificate chain.";
        }      
        leaf attestation-certificate {
          type ietfct:end-entity-cert-cms;
          description
            "The binary signed certificate chain data for this identity
            certificate.";
        }
        uses tpm20-attestation-key-identifier;
      }
    }
  }
  
  rpc log-retrieval {
    description
      "Logs Entries are either identified via indices or via providing
      the last line received. The number of lines returned can be
      limited. The type of log is a choice that can be augmented.";
    input {
      list log-selector {
        key node-name;
        description
          "Selection of log entries to be reported.";
        uses compute-node;
        choice index-type {
          description
            "Last log entry received, log index number, or timestamp.";
          case last-entry {
            description
              "The last entry of the log already retrieved.";
            leaf last-entry-value {
              type binary;
              description
                "Content of an log event which matches 1:1 with a 
                unique event record contained within the log.  Log 
                entries subsequent to this will be passed to the 
                requester.  Note: if log entry values are not unique, 
                this MUST return an error.";
            }
          }
          case index {
            description
              "Numeric index of the last log entry retrieved, or zero.";
            leaf index-number {
              type uint64;
              description
                "The numeric index number of a log entry.  Zero means 
                to start at the beginning of the log.   Entries
                subsequent to this will be passed to the 
                requester.";
            }
          }
          case timestamp {
            leaf timestamp {
              type yang:date-and-time;
              description
                "Timestamp from which to start the extraction.  The next
                log entry subsequent to this timestamp is to be sent.";
            }
            description
              "Timestamp from which to start the extraction.";
          }
        }
      }
      uses log-identifier;
      uses tpm20-pcr-selection;
      leaf log-entry-quantity {
        type uint16;
        description
          "The number of log entries to be returned. If omitted, it 
          means all of them.";
      }
    } 
    output {
      container system-event-logs {
        description
          "The requested data of the measurement event logs";
        list node-data {
          key "node-name tpm_name";
          description
            "Event logs of a node in a distributed system
             identified by the node name";
          uses compute-node;
          uses node-uptime;
	  uses tpm-name;
          container log-result {
            description
              "The requested entries of the corresponding log.";
            uses event-logs;
          }
        }
      }
    }
  }

  container rats-support-structures {
    config false;
    description
      "The datastore definition enabling verifiers or relying parties to discover the information necessary to use the remote attestation RPCs appropriately.";

    leaf-list supported-algos {
      type uint16;
      description
        "Supported TPM_ALG_ID values for the TPM in question.
        Will include ComponentIndex soon.";
    }

    list compute-nodes {
      key node-id;
      uses compute-node-identifier;
      description
	"A list names of hardware componnets in this composite device that RATS can be conducted with.";
      
      leaf node-name {
        type string;
	description
	  "Name of the compute node.";
      }

      leaf node-location {
	type string;
	description
	  "Location of the compute node, such as slot number.";
      }    
    
      list tpms {
        key tpm-name;
        uses tpm-identifier;
        description
      	  "A list of TPMs in this composite device that rats can be conducted with.";

	leaf tpm-manufacturer {
	  type string;
	  description
	    "TPM manufacturer name.";
	}

	leaf tpm-firmware-version {
	  type string;
	  description 
	    "TPM firmware version.";
	}

	leaf tpm-specification-version {
	  type string;
	  description 
	    "TPM1.2 or TPM2.0.";
	}

	leaf tpm-status {
	  type string;
	  description
	    "TPM chip self-test status, normal or abnormal.";
	}

        list certificates {
          description
	    "The TPM's certificates, including EK certificates and AK certificates.";
	  container certificate {
	    description
		"Three types of certificates can be accessed via this statement, including Initial Attestation Key Cert, Local Attestation Key Cert or Endorsement Key Cert.";
    	    leaf certificate-name {
              type string;
              description
                "An arbitrary name for this identity certificate or
                certificate chain.";
            }
	    leaf certificate-type {
	      type enumeration {
	        enum endorsement-cert {
		     value 0;
		     description
			"EK Cert type.";
		}
		enum initial-attestation-cert {
		     value 1;
		     description
			"IAK Cert type";
		}
		enum local-attestation-cert {
		     value 2;
		     description
			"LAK Cert type";
		}
	      }
	      description  "Type of this certificate";
	    }

            leaf certificate-value {
              type ietfct:end-entity-cert-cms;
              description
    	    	"The binary signed public endorsement key (EK), attestation key(AK) and corresponding
                claims (EK,AK Certificate). In a TPM 2.0 the EK,AK Certificate
                resides in a well-defined NVRAM location by the TPM vendor.
		Maybe certificate-value defined as binary type is a simple way.";
            }

	    leaf lak-public-structure {
	      type binary;
	      description
		"Marshalled LAK public structure, used for LAK Cert verification";
    	    }
	}
      }
    }
  }
}
